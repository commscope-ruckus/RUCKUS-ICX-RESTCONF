module icx-openconfig-system-dev{

  yang-version "1.1";
  
  //namespace
  namespace "http://commscope.com/ns/yang/icx/icx-openconfig-system-dev";
  
  prefix "icx-openconfig-system-dev";

  // import some basic types
  import openconfig-extensions { prefix oc-ext; }
  import openconfig-system { prefix oc-sys; }

  // meta
  organization "Commscope Holding Company Inc.";

  contact
    "Commscope Support Group";

  description
    "This module defines a YANG data model deviation for 
     unsupported configurations and operational state data from 
     openconfig-system.yang.
    Copyright (c) 2018-2020 by Commscope Holding Company Inc.
    All rights reserved.";

  revision "2019-09-04" {
    description
      "initial deviation for unsupported configurations and 
       operational state data from openconfig-system.yang";
    reference "0.1.0";
  }

  /* *******************************************************************
   * Configuration Deviations 
   * ******************************************************************/

  deviation "/oc-sys:system/oc-sys:dns/oc-sys:servers/oc-sys:server/oc-sys:config/oc-sys:port" {
    deviate "not-supported";
    }

  deviation "/oc-sys:system/oc-sys:dns/oc-sys:servers/oc-sys:server/oc-sys:state/oc-sys:port" {
    deviate "not-supported";
    }

  deviation "/oc-sys:system/oc-sys:dns/oc-sys:servers/oc-sys:server" {
    deviate add {
      max-elements 4;
      }
    }

}
