module icx-openconfig-if-ip-dev {
    yang-version 1.1;
    
    //namespace
    namespace "http://commscope.com/ns/yang/icx/icx-openconfig-if-ip";

    prefix "icx-openconfig-if-ip-dev";
    
    import openconfig-interfaces { prefix oc-if; }
    import openconfig-vlan { prefix oc-vlan; }
    import openconfig-if-ip { prefix oc-ip; }

    //meta
    organization "Commscope Holding Company Inc.";

    contact "Commscope Support Group";

    description "This model defines deviation YANG data model that can be
        used to configure and manage a IP Address for ICX family products based on openconfig YANG model.
        Copyright (c) 2018-2020 by Commscope Holding Company Inc
        All rights reserved.";

    revision 2019-08-06 {
        description "Initial of the ICX Openconfig IP Address Deviation YANG model.";
        reference "0.1.0";
    }
    

    // Module Deviations
    deviation "/oc-if:interfaces/oc-if:interface/oc-if:subinterfaces/oc-if:subinterface/oc-ip:ipv6" { 
        deviate "not-supported";
    }
    deviation "/oc-if:interfaces/oc-if:interface/oc-if:subinterfaces/oc-if:subinterface/oc-if:state" {
	deviate "not-supported";
    }
    deviation "/oc-if:interfaces/oc-if:interface/oc-if:subinterfaces/oc-if:subinterface/oc-ip:ipv4/oc-ip:proxy-arp" { 
        deviate "not-supported";
    }
    deviation "/oc-if:interfaces/oc-if:interface/oc-if:subinterfaces/oc-if:subinterface/oc-ip:ipv4/oc-ip:neighbors" { 
        deviate "not-supported";
    }
    deviation "/oc-if:interfaces/oc-if:interface/oc-if:subinterfaces/oc-if:subinterface/oc-ip:ipv4/oc-ip:unnumbered" { 
        deviate "not-supported";
    }
    deviation "/oc-if:interfaces/oc-if:interface/oc-if:subinterfaces/oc-if:subinterface/oc-ip:ipv4/oc-ip:config" { 
        deviate "not-supported";
    }
    deviation "/oc-if:interfaces/oc-if:interface/oc-if:subinterfaces/oc-if:subinterface/oc-ip:ipv4/oc-ip:state" { 
        deviate "not-supported";
    }
    deviation "/oc-if:interfaces/oc-if:interface/oc-if:subinterfaces/oc-if:subinterface/oc-ip:ipv4" + 
        "/oc-ip:addresses/oc-ip:address/oc-ip:state" { 
        deviate "not-supported";
    }
    deviation "/oc-if:interfaces/oc-if:interface/oc-if:subinterfaces/oc-if:subinterface/oc-ip:ipv4" + 
        "/oc-ip:addresses/oc-ip:address/oc-ip:vrrp" { 
        deviate "not-supported";
    }
    deviation "/oc-if:interfaces/oc-if:interface/oc-vlan:routed-vlan/oc-ip:ipv6" { 
        deviate "not-supported";
    }
    deviation "/oc-if:interfaces/oc-if:interface/oc-vlan:routed-vlan/oc-ip:ipv4/oc-ip:proxy-arp" { 
        deviate "not-supported";
    }
    deviation "/oc-if:interfaces/oc-if:interface/oc-vlan:routed-vlan/oc-ip:ipv4/oc-ip:neighbors" { 
        deviate "not-supported";
    }
    deviation "/oc-if:interfaces/oc-if:interface/oc-vlan:routed-vlan/oc-ip:ipv4/oc-ip:unnumbered" { 
        deviate "not-supported";
    }
    deviation "/oc-if:interfaces/oc-if:interface/oc-vlan:routed-vlan/oc-ip:ipv4/oc-ip:config" { 
        deviate "not-supported";
    }
    deviation "/oc-if:interfaces/oc-if:interface/oc-vlan:routed-vlan/oc-ip:ipv4/oc-ip:state" { 
        deviate "not-supported";
    }
    deviation "/oc-if:interfaces/oc-if:interface/oc-vlan:routed-vlan/oc-ip:ipv4/oc-ip:addresses" + 
        "/oc-ip:address/oc-ip:state" { 
        deviate "not-supported";
    }
    deviation "/oc-if:interfaces/oc-if:interface/oc-vlan:routed-vlan/oc-ip:ipv4/oc-ip:addresses" + 
        "/oc-ip:address/oc-ip:vrrp" { 
        deviate "not-supported";
    }
}
