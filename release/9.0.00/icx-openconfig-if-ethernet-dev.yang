module icx-openconfig-if-ethernet-dev {

  yang-version "1.1";

  // namespace
  namespace "http://commscope.com/ns/yang/icx/icx-openconfig-if-ethernet-dev";

  prefix "icx-oc-eth-dev";

  // import some basic types
  import openconfig-interfaces { prefix oc-if; }
  import openconfig-if-ethernet {prefix oc-eth; }

  // meta
  organization "Commscope Holding Company Inc.";

  contact
    "Commscope Support Group";

  description
    "This YANG data-model is deviation from openconfig-if-ethernet YANG data-model
    for ICX Switches/Router family of products.
    Copyright (c) 2018-2020 by Commscope Holding Company Inc.
    All rights reserved.";


  revision "2019-10-11" {
    description
    "Initial of deviation from the ICX Openconfig/if-ethernet Augmentation YANG model.";
        reference "0.1.0";
  }

  /********************************************************************
   * Deviations
   *******************************************************************/
   deviation "/oc-if:interfaces/oc-if:interface/oc-eth:ethernet/oc-eth:config/oc-eth:mac-address" {
      deviate "not-supported";
   }

  deviation "/oc-if:interfaces/oc-if:interface/oc-eth:ethernet/oc-eth:state/oc-eth:counters" {
      deviate "not-supported";
  }
}
